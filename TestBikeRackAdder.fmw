FME workspace TestBikeRackAdder.fmw

Parameters:
- SourceDataset_POSTGIS = bikeracks-production   # Connection
- DestDataset_HTML = $(FME_SHAREDRESOURCE_TEMP)/BikeRackAdderTestOutput.html   # HTML Files(*.html)|*.html Destination Html File
- GoodRecord_Title = Good Bike Rack Title   # "" GoodRecord Title
- GoodRecord_Description = Good Bike Rack Description   # "" GoodRecord Description
- GoodRecord_Capacity = 5   # GoodRecord Capacity
- GoodRecord_Host = Good Bike Rack Host   # "" GoodRecord Host
- FME_SHAREDRESOURCE_TEMP = ../Resources/Temp   # FME Server Temporary Resource Directory

Readers:
- POSTGIS_1: POSTGIS from $(SourceDataset_POSTGIS)

Writers:
- HTML_1: HTML to $(DestDataset_HTML)

Note: Create mock feature to test adding a bike rack to the database.
GoodRecordCreator: Creator
    GEOMTYPE = Geometry Object
    NUM = 1
    CREATED -> GoodBikeRackDeleter
GoodBikeRackDeleter
    GoodRecord_Capacity = $(GoodRecord_Capacity)
    GoodRecord_Description = $(GoodRecord_Description)
    GoodRecord_Host = $(GoodRecord_Host)
    GoodRecord_Title = $(GoodRecord_Title)
    -> GoodBikeRackAdder
GoodBikeRackAdder
    -> GoodBikeRackAddedVerifier
GoodBikeRackAddedVerifier: GoodBikeRackVerifier
    GoodRecord_Capacity = $(GoodRecord_Capacity)
    GoodRecord_Description = $(GoodRecord_Description)
    GoodRecord_Host = $(GoodRecord_Host)
    GoodRecord_Title = $(GoodRecord_Title)
    -> AttributeValidationHTMLReportGenerator

Bookmark: Generate & write validation report.
AttributeValidationHTMLReportGenerator
    _FEATURE_ID = @Value(id)
    -> HTML (writer HTML_1)
HTML (writer HTML_1)
    attributes: html_content buffer

FME custom transformer BikeRackExistenceTester

Parameters:
- TITLE = @Value(title)   # Mode,WHERE title
- DESCRIPTION = @Value(description)   # Mode,WHERE description
- CAPACITY = @Value(capacity)   # Mode,WHERE capacity
- HOST = @Value(host)   # Mode,WHERE host

Input (input)
    -> FeatureReader [INITIATOR]
FeatureReader
    ATTRIBUTES = public.bikeracks,"id,title,description,capacity,host"
    ATTR_ACCUM_MODE = Only Use Result
    COMBINE_GEOM = Use Result
    DATASET = bikeracks-production
    FEATURETYPES = public.bikeracks
    FORMAT = POSTGIS
    INTERACT = Initiator Equals Result
    MAX_FEATURES = 1
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = bikeracks-production
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    WHERE = "title" = '@Value(title)' and "description" = '@Value(description)' and "capacity" = @Value(capacity) and "host" = '@Value(host)'
    <SCHEMA> -> <Schema> (output)
    public.bikeracks -> BikeRack (output)
    <OTHER> -> <Generic> (output)
    INITIATOR -> <Initiator> (output)
    <REJECTED> -> <Rejected> (output)
<Schema> (output)
BikeRack (output)
<Generic> (output)
<Initiator> (output)
<Rejected> (output)

FME custom transformer NoFeaturesTester
This transformer checks whether there are any input features. If not, then a single feature is ouput via the NOINPUT port. If INPUT features exist, then they are output via the INPUT output port.
Other transformers often generate features that signify an error condition. This transformer can be used to check for those features and if those features exists, then a separate action can be triggered.
    Example
This may be useful to test if any data emerges from a reader, when the 'Ignore Failed Readers' advanced parameter is set to yes.
Input Ports
    Input
Features to be checked for existence
    Output Ports
    NoInput
If no Input features exist, a single featue is returned via the NoInput port
    Output
Any feature that entered the Input port is returned via the Output port

INPUT (input)
    -> Sampler
    -> OUTPUT (output)
OUTPUT (output)
Sampler
    RATE = 1
    SAMPLE_MODE = No
    SAMPLE_TYPE_LONG = First N Features
    SAMPLED -> AttributeCreator_2
AttributeCreator_2
    ATTR_TABLE:
      SET_TO count = 0
      SET_TO remove = yes
    -> DuplicateFilter
Creator
    GEOMTYPE = Geometry Object
    NUM = 1
    CREATED -> AttributeCreator_3
AttributeCreator_3
    ATTR_TABLE = SET_TO no_features = true
    -> DuplicateFilter
DuplicateFilter
    INPUT_ORDERED_CHOICE = No
    KEYATTR = count
    UNIQUE -> Tester
Tester
    BOOL_OP = OR
    TEST_CLAUSE = TEST @Value(remove) != yes
    TEST_MODE = Automatic
    PASSED -> AttributeRemover
AttributeRemover
    REMOVE_ATTRS = count,remove
    -> NOINPUT (output)
NOINPUT (output)

FME custom transformer BikeRackAdder

Input (input)
    -> FeatureWriter [public.bikeracks]
FeatureWriter
    DATASET = bikeracks-production
    DATASET_ATTR = _dataset
    FEATURE_TYPE_LIST_ATTR = _feature_type
    FORMAT = POSTGIS
    POSTGIS_BULK_COPY = YES
    POSTGIS_COORDINATE_SYSTEM_GRANULARITY = FEATURE_TYPE
    POSTGIS_GENERIC_GEOMETRY = yes
    POSTGIS_INSERT_TEXT_GEOMETRY = NO
    POSTGIS_LOWERCASE_ATTRIBUTE_NAMES = Yes
    POSTGIS_NAMED_CONNECTION = bikeracks-production
    POSTGIS_SPATIAL_COLUMN_NAME = geom
    POSTGIS_SPATIAL_COLUMN_TYPE = geometry
    POSTGIS_START_TRANSACTION = 0
    POSTGIS_STRICT_TEMPORAL_TYPE_HANDLING = Yes
    POSTGIS_TRANSACTION_INTERVAL = 1000
    TOTAL_FEATURES_WRITTEN_ATTR = _total_features_written
    public.bikeracks -> BikeRack (output)
    SUMMARY -> Summary (output)
BikeRack (output)
Summary (output)

FME custom transformer AttributeValidationListPopulator
Enhance the output from a standard AttributeValidator transformer with contextual information to assist subsequent diagnosis of invalid attribute values.  The output is meant to be used by a subsequent AttributeValidationHTMLReportGenerator to create a human-readable report of invalid attributes at different positions within a calling workspace or custom transformer.
IMPORTANT: This transformer must be embedded, not linked, for the calling module (workspace or linked custom transformer) to be properly identified; this is the default when you add it to your workflow.
This transformer is part of a suite that can be used for both data and workflow quality.  For the former, data can be tested and exception reports generated from inside any workspace or transformer.  For the latter, regression test driver workspaces can call a target workspace or transformer with predefined test data and verify that the results are correct and can be generated without error for both common and edge cases.
For issues or questions, please Create an issue here.  For the source, including test driver components, please see the Github repository.
Copyright © 2019 by Modern geoSystems, released under this BSD 3-clause license.
Ports
Input
Feed all features that have just been tested with a standard AttributeValidator transformer.
Output
The input feature enhanced with the following list attributes:
_fme_validation_message_list{}.validator_name - The name or prefix of the AttributeValidator, as provided in the Validator_Name parameter, that detected the error with the corresponding element in _fme_validation_message_list{}
_fme_validation_message_list{}.calling_module - The name of the workspace or linked custom transformer where the named validator exists
Parameters
Specify the required yet unknown values for the preceding AttributeValidator.
Validator_Name
The name or prefix of the preceding AttributeValidator.

Parameters:
- Validator_Name =   # Validator Name

Input (input)
    -> ParameterFetcher
ParameterFetcher
    ATTR_LIST = _FME_MF_DIR $(FME_MF_DIR_USERTYPED) _FME_MF_NAME $(FME_MF_NAME)
    -> AttributeCreator
AttributeCreator
    ATTR_TABLE:
      SET_TO _mgs_calling_module = @Value(_FME_MF_DIR)@Value(_FME_MF_NAME)
      SET_TO _mgs_validator_name = $(Validator_Name)
    -> PythonCaller
PythonCaller
    NEW_ATTRIBUTES = _fme_validation_message_list{}.validator_name _fme_validation_message_list{}.calling_module
    PYTHONSOURCE:
      import fme
      import fmeobjects

      def processFeature(feature):
          messages = feature.getAttribute('_fme_validation_message_list')
          if messages:
              index = 0
              for message in messages:
                  if feature.getAttributeNullMissingAndType('_fme_validation_message_list{' + str(index) + '}.validator_name')[1]:
                      feature.setAttribute('_fme_validation_message_list{' + str(index) + '}.validator_name', feature.getAttribute('_mgs_validator_name'))
                      feature.setAttribute('_fme_validation_message_list{' + str(index) + '}.calling_module', feature.getAttribute('_mgs_calling_module'))
                  index += 1
    PYTHONSYMBOL = processFeature
    -> AttributeExposer
AttributeExposer
    ATTR_LIST = _fme_validation_message
    -> AttributeRemover_2
AttributeRemover_2
    REMOVE_ATTRS = _mgs_validator_name,_fme_validation_message,_FME_MF_DIR,_FME_MF_NAME,_mgs_calling_module
    -> Output (output)
Output (output)

FME custom transformer BikeRackContentGenerator

Parameters:
- GoodRecord_Title = MGS Post Test   # GoodRecord Title
- GoodRecord_Description = This is a POST test.   # GoodRecord Description
- GoodRecord_Capacity = 5   # GoodRecord Capacity
- GoodRecord_Host = Modern geoSystems   # GoodRecord Host

Input (input)
    -> AttributeManager
AttributeManager
    ATTR_TABLE:
      SET_TO fme_feature_type = public.bikeracks
      SET_TO title = $(GoodRecord_Title)
      SET_TO description = $(GoodRecord_Description)
      SET_TO capacity = $(GoodRecord_Capacity)
      SET_TO host = $(GoodRecord_Host)
    -> VertexCreator
VertexCreator
    MEASURE_TYPE = Continuous
    MISSING_VAL_MODE = Compute
    MODE_NAME = Add Point
    XVAL = -105.086648
    YVAL = 39
    -> CoordinateSystemSetter
CoordinateSystemSetter
    COORDSYS = EPSG:4326
    -> Output (output)
Output (output)

FME custom transformer GoodBikeRackDeleter
Delete good bike rack & verify same.

Parameters:
- GoodRecord_Title = MGS Post Test   # GoodRecord Title
- GoodRecord_Description = This is a POST test.   # GoodRecord Description
- GoodRecord_Capacity = 5   # GoodRecord Capacity
- GoodRecord_Host = Modern geoSystems   # GoodRecord Host

Input (input)
    -> PreDeleteBikeRackContentGenerator
PreDeleteBikeRackContentGenerator: BikeRackContentGenerator
    GoodRecord_Capacity = $(GoodRecord_Capacity)
    GoodRecord_Description = $(GoodRecord_Description)
    GoodRecord_Host = $(GoodRecord_Host)
    GoodRecord_Title = $(GoodRecord_Title)
    -> DeletionFeatureWriter [public.bikeracks]
DeletionFeatureWriter: FeatureWriter
    DATASET = bikeracks-production
    DATASET_ATTR = _dataset
    FEATURE_TYPE_LIST_ATTR = _feature_type
    FORMAT = POSTGIS
    POSTGIS_BULK_COPY = YES
    POSTGIS_COORDINATE_SYSTEM_GRANULARITY = FEATURE_TYPE
    POSTGIS_GENERIC_GEOMETRY = yes
    POSTGIS_INSERT_TEXT_GEOMETRY = NO
    POSTGIS_LOWERCASE_ATTRIBUTE_NAMES = Yes
    POSTGIS_NAMED_CONNECTION = bikeracks-production
    POSTGIS_SPATIAL_COLUMN_NAME = geom
    POSTGIS_SPATIAL_COLUMN_TYPE = geometry
    POSTGIS_START_TRANSACTION = 0
    POSTGIS_STRICT_TEMPORAL_TYPE_HANDLING = Yes
    POSTGIS_TRANSACTION_INTERVAL = 1000
    TOTAL_FEATURES_WRITTEN_ATTR = _total_features_written
    SUMMARY -> PostDeleteBikeRackContentGenerator
PostDeleteBikeRackContentGenerator: BikeRackContentGenerator
    GoodRecord_Capacity = $(GoodRecord_Capacity)
    GoodRecord_Description = $(GoodRecord_Description)
    GoodRecord_Host = $(GoodRecord_Host)
    GoodRecord_Title = $(GoodRecord_Title)
    -> BikeRackExistenceTester
BikeRackExistenceTester
    CAPACITY = @Value(capacity)
    DESCRIPTION = @Value(description)
    HOST = @Value(host)
    TITLE = @Value(title)
    <Initiator> -> AttributeValidator
AttributeValidator
    TABLE = _matched_records;IN;0
    PASSED -> AttributeValidationListPopulator
    FAILED -> AttributeValidationListPopulator
AttributeValidationListPopulator
    Validator_Name = GoodBikeRackDeleter
    -> DummyIDAttributeCreator
DummyIDAttributeCreator: AttributeCreator
    ATTR_TABLE = SET_TO id = FME_NULL_VALUE
    -> Output (output)
Output (output)

FME custom transformer GoodBikeRackAdder
Add good bike rack & verify.

Input (input)
    -> BikeRackAdder
BikeRackAdder
    Summary -> AttributeValidator
AttributeValidator
    TABLE = _total_features_written;IN;1
    PASSED -> AttributeValidationListPopulator
    FAILED -> AttributeValidationListPopulator
AttributeValidationListPopulator
    Validator_Name = GoodBikeRackAdder
    -> Output (output)
Output (output)

FME custom transformer GoodBikeRackVerifier
Read back good bike rack & validate.

Parameters:
- GoodRecord_Title = MGS Post Test   # GoodRecord Title
- GoodRecord_Description = This is a POST test.   # GoodRecord Description
- GoodRecord_Capacity = 5   # GoodRecord Capacity
- GoodRecord_Host = Modern geoSystems   # GoodRecord Host

Input (input)
    -> BikeRackContentGenerator
BikeRackContentGenerator
    GoodRecord_Capacity = $(GoodRecord_Capacity)
    GoodRecord_Description = $(GoodRecord_Description)
    GoodRecord_Host = $(GoodRecord_Host)
    GoodRecord_Title = $(GoodRecord_Title)
    -> BikeRackExistenceTester
BikeRackExistenceTester
    CAPACITY = @Value(capacity)
    DESCRIPTION = @Value(description)
    HOST = @Value(host)
    TITLE = @Value(title)
    BikeRack -> NoFeaturesTester
NoFeaturesTester
    NOINPUT -> AttributeValidator
    -> NoFeaturesFalseAttributeCreator
NoFeaturesFalseAttributeCreator: AttributeCreator
    ATTR_TABLE = SET_TO no_features = false
    -> AttributeValidator
AttributeValidator
    TABLE = no_features;IN;false/title;IN;$(GoodRecord_Title)/description;IN;$(GoodRecord_Description)/capacity;IN;$(GoodRecord_Capacity)/host;IN;$(GoodRecord_Host)
    PASSED -> AttributeValidationListPopulator
    FAILED -> AttributeValidationListPopulator
AttributeValidationListPopulator
    Validator_Name = GoodBikeRackVerifier
    -> Output (output)
Output (output)
