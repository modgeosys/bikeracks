FME workspace PostBikeRack.fmw

Parameters:
- Title = Title
- Description = Description   # " " Description
- Capacity = 10
- Host = Host
- FMEEXPRESS_LOCATION_ = {"latitude":39.5484347,"longitude":-104.5484347}   # Location
- Longitude:   # Python Script
      import json
      location = json.loads(FME_MacroValues['FMEEXPRESS_LOCATION_'])
      return float(location['longitude'])
- Latitude:   # Python Script
      import json
      location = json.loads(FME_MacroValues['FMEEXPRESS_LOCATION_'])
      return float(location['latitude'])
- DestDataset_HTML = $(FME_SHAREDRESOURCE_TEMP)/PostBikeRackOutput.html   # HTML Files(*.html)|*.html Destination Html File
- FME_SHAREDRESOURCE_TEMP = /home/kweller/Projects/mg/bikeracks/fme/Resources/Temp/   # FME Server Temporary Resource Directory
- FME_SHAREDRESOURCE_DATA = /home/kweller/Projects/mg/bikeracks/fme/Resources/Data/   # FME Server Data Directory

Writers:
- HTML_1: HTML to $(DestDataset_HTML)

Creator
    GEOMTYPE = Geometry Object
    NUM = 1
    CREATED -> ParameterFetcher
Note: Extract new bike rack feature attributes from workspace parameters.
ParameterFetcher
    ATTR_LIST = title $(Title) description $(Description) capacity $(Capacity) host $(Host) longitude $(Longitude) latitude $(Latitude)
    -> BikeRackAdder
Note: Add the bike rack to the database.
BikeRackAdder
    CAPACITY = @Value(capacity)
    DESCRIPTION = @Value(description)
    Dataset_POSTGIS = bikeracks-development
    HOST = @Value(host)
    LATITUDE = @Value(latitude)
    LONGITUDE = @Value(longitude)
    TITLE = @Value(title)
    BikeRack -> HTMLReportGenerator
    Summary -> NoOutputTester
    <INVALID> -> AttributeValidationHTMLReportGenerator
Note: Notify user of success.
HTMLReportGenerator
    CONTENT_LIST = HEADER SEPARATOR TABLE
    PAGE_CONFIG = HEADER{{TEXT;Bike rack successfully added!;HEADER;H1;HEADER_ID;;ALIGNMENT;LEFT;COLOR;0,0,0;FME_CONTROLLER_QUERY_FILE;transformers/dependencies/html5/Header.fme}}SEPARATOR{{WIDTH;1;FME_CONTROLLER_QUERY_FILE;transformers/dependencies/html5/Separator.fme}}TABLE{{STYLE;STRIPED;TABLE;title|Title/description|Description/capacity|Capacity/host|Host;FME_CONTROLLER_QUERY_FILE;transformers/dependencies/html5/Table.fme}}
    TITLE = Bike Rack successfully added!
    -> HTML (writer HTML_1)
NoOutputTester: Tester
    BOOL_OP = OR
    COMPOSITE_TEST = 1
    TEST_CLAUSE = TEST @Value(_total_features_written) = 0
    TEST_MODE = TEST
    PASSED -> ErrorHTMLReportGenerator
Note: Notify user of general error.
ErrorHTMLReportGenerator: HTMLReportGenerator
    CONTENT_LIST = HEADER
    PAGE_CONFIG = HEADER{{TEXT;ERROR:  Bike rack addition failed!;HEADER;H1;HEADER_ID;;ALIGNMENT;LEFT;COLOR;255,0,0;FME_CONTROLLER_QUERY_FILE;transformers/dependencies/html5/Header.fme}}
    TITLE = Bike rack addition failed!
    -> HTML (writer HTML_1)
Note: Notify user of any validation errors.
AttributeValidationHTMLReportGenerator
    _FEATURE_ID = N/A
    -> ValidationErrorsTester
Note: Only output validation report when there are invalid attributes.
ValidationErrorsTester: Tester
    BOOL_OP = OR
    COMPOSITE_TEST = 1
    TEST_CLAUSE = TEST _no_validation_errors NOT_ATTRIBUTE_HAS_A_VALUE ""
    TEST_MODE = TEST
    PASSED -> HTML (writer HTML_1)
HTML (writer HTML_1)
    attributes: html_content buffer
